(DEFUN C:Durys()
  (setq taskas (getpoint "\nIveskite bazinio tasko pradine koordinate:"))
    (COMMAND "CHPROP" sel "" "COLOR" "BYLAYER" "LWEIGHT" "0.30" "LTYPE" "BYLAYER" "")
  (setq I01 (list (+ (car taskas) 50) (+ (cadr taskas) 0)))
  (setq I02 (list (+ (car taskas) 0) (+ (cadr taskas) 120)))
  (setq I03 (list (+ (car taskas) 50) (+ (cadr taskas) 120)))
  (setq P01 (list (+ (car I02) 15) (- (cadr I02) 25)))
  (setq P02 (list (- (car I03) 15) (- (cadr I03) 25)))
  (setq R01 (list (- (car P01) 3) (- (cadr P01) 23)))
  (setq R02 (list (- (car P01) 3) (+ (cadr P01) 23)))
  (setq R03 (list (+ (car P02) 3) (- (cadr P02) 23)))
  (setq R04 (list (+ (car P02) 3) (+ (cadr P02) 23)))
  (setq R11 (list (+ (car R01) 3) (+ (cadr R01) 3)))
  (setq R12 (list (+ (car R02) 3) (- (cadr R02) 3)))
  (setq R13 (list (- (car R03) 3) (+ (cadr R03) 3)))
  (setq R14 (list (- (car R04) 3) (- (cadr R04) 3)))
  (command "line" R01 R11 -enter)
  (command "line" R02 R12 -enter)
  (command "line" R03 R13 -enter)
  (command "line" R04 R14 -enter)
  (command "line" R01 R02 R04 R03 R01 -enter)
  (command "Rectangle" taskas I03 -enter)
  (command "pline" P01 "w" 40 40 P02 -enter)
  (setq rankena (list (+ (car taskas) 42) (+ (cadr taskas) 68)))
  (command "circle" rankena 3 -enter)
  (command "circle" rankena 1 -enter)
  (setq Z1 (list (+ (car taskas) 5)  (+ (cadr taskas) 5)))
  (setq Z2 (list (+ (car taskas) 45) (+ (cadr taskas) 5)))
  (setq Z3 (list (+ (car taskas) 5)  (+ (cadr taskas) 30)))
  (setq Z4 (list (+ (car taskas) 45) (+ (cadr taskas) 30)))
  (setq Z5 (list (+ (car taskas) 10) (+ (cadr taskas) 10)))
  (setq Z6 (list (+ (car taskas) 40) (+ (cadr taskas) 10)))
  (setq Z7 (list (+ (car taskas) 10) (+ (cadr taskas) 25)))
  (setq Z8 (list (+ (car taskas) 40) (+ (cadr taskas) 25)))
  (command "line" Z1 Z2 Z4 Z3 "c")
  (command "line" Z5 Z6 Z8 Z7 "c")
  (command "line" Z1 Z5 -enter)
  (command "line" Z2 Z6 -enter)
  (command "line" Z3 Z7 -enter)
  (command "line" Z4 Z8 -enter)
  (setq Q1 (list (+ (car taskas) 5) (+ (cadr taskas) 35)))
  (setq Q2 (list (+ (car taskas) 45) (+ (cadr taskas) 35)))
  (setq Q3 (list (+ (car taskas) 5) (+ (cadr taskas) 60)))
  (setq Q4 (list (+ (car taskas) 45) (+ (cadr taskas) 60)))
  (setq Q5 (list (+ (car taskas) 10) (+ (cadr taskas) 40)))
  (setq Q6 (list (+ (car taskas) 40) (+ (cadr taskas) 40)))
  (setq Q7 (list (+ (car taskas) 10) (+ (cadr taskas) 55)))
  (setq Q8 (list (+ (car taskas) 40) (+ (cadr taskas) 55)))
  (command "line" Q1 Q2 Q4 Q3 "c")
  (command "line" Q5 Q6 Q8 Q7 "c")
  (command "line" Q1 Q5 -enter)
  (command "line" Q2 Q6 -enter)
  (command "line" Q3 Q7 -enter)
  (command "line" Q4 Q8 -enter)
  (command "fillet" "R" (/ 3) )
  (command "fillet"  (list(+ (car I02) 3) (cadr I02) )  (list (car I02) (-(cadr I02) 3)) -enter)
  (command "fillet"  (list(- (car I03) 3) (cadr I03) )  (list (car I03) (-(cadr I03) 3)) -enter)
  (command "fillet"  (list(- (car I01) 3) (cadr I01) )  (list (car I01) (+(cadr I01) 3)) -enter)
  (command "fillet"  (list(+ (car taskas) 3) (cadr taskas) )  (list (car taskas) (+(cadr taskas) 3)) -enter)
)

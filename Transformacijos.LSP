; perkelimo transformacijos matrica
(defun c:perkelimas(/ x1 y1 x2 y2 x3 y3 xx1 yy1 xx2 yy2 xx3 yy3 xxx1 yyy1 xxx2 yyy2
	    x y m11 m12 m13 m21 m22 m23 m31 m32 m33 TX TY perkelimass)
(setq x1 2 y1 6 x2 6 y2 10 x3 6 y3 2)
(command "color" "Red" )
(setq variantas1 (getint "\nNurodykite varianta - iveskite destytojo nurodyta numeri: "))
(setq perkelimass (rem variantas1 4))
  (if (= perkelimass 0) (setq TX 6 TY 4)) (if (= perkelimass 1) (setq TX 8 TY 6))
  (if (= perkelimass 2) (setq TX 8 TY 8)) (if (= perkelimass 3) (setq TX 6 TY 6))
  (setq xx1 (+ x1 TX) yy1 (+ y1 TY) xx2 (+ x2 TX) yy2 (+ y2 TY) xx3 (+ x3 TX) yy3 (+ y3 TY))
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) "c")
(command "line" (list xx1 yy1) (list xx2 yy2) (list xx3 yy3) "c")
(command "color" "Red" )
(command "text" "j" "mc"(list (+ x1 2) y1)  0.8 0 "Yra")
(command "text" "j" "mc"(list (+ xx1 2) yy1)  0.6 0 "Reikia")
(prompt "\nIveskite perkelimo transformacijos matricos 1-os eilutes elementus:")
  (setq M11 (getreal "\n1-ojo elemento reiksme: "))
  (setq M12 (getreal "2-ojo elemento reiksme: "))
  (setq M13 (getreal "3-ojo elemento reiksme: "))
(prompt "\nIveskite perkelimo transformacijos matricos 2-os eilutes elementus:")
  (setq M21 (getreal "\n1-ojo elemento reiksme: "))
  (setq M22 (getreal "2-ojo elemento reiksme: "))
  (setq M23 (getreal "3-ojo elemento reiksme: "))
(prompt "\nIveskite perkelimo transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* TX 1))) (setq yyy1 (+ (* x1 M12) (* y1 M22) (* TY 1)))
(setq xxx2 (+ (* x2 M11) (* y2 M21) (* TX 1))) (setq yyy2 (+ (* x2 M12) (* y2 M22) (* TY 1)))
(setq xxx3 (+ (* x3 M11) (* y3 M21) (* TX 1))) (setq yyy3 (+ (* x3 M12) (* y3 M22) (* TY 1)))
(command "color" "Red" )
(if (and (= xxx1 xx1) (= yyy1 yy1) (= xxx2 xx2) (= yyy2 yy2)(= xxx3 xx3)(= yyy3 yy3)
	 (= M31 TX) (= M32 TY) (= M33 1)) (setq rezultatas1 1) (setq rezultatas1 0))
(if (= rezultatas1 1)  (command "text" (list 2 17) 2.5 0 "TEISINGAI!")
                       (command "text" (list 2 17) 2.5 0 "KLAIDINGAI!"))
(command "pline" (list xxx1 yyy1) "w" 0.2 0.2 (list xxx2 yyy2) (list xxx3 yyy3) "c")
)
; pasukimo transformacijos matrica
(defun c:pasukimas(/ x1 y1 x2 y2 x3 y3 xx1 yy1 xx2 yy2 xx3 yy3 xxx1 yyy1 xxx2 yyy2
	    x y m11 m12 m13 m21 m22 m23 m31 m32 m33 TX TY pasukimass)
(setq x1 0 y1 0 x2 8 y2 -4 x3 8 y3 4)
(command "color" "Red" )
(setq variantas2 (getint "\nNurodykite varianta - iveskite destytojo nurodyta numeri: "))
(setq pasukimass (rem variantas2 3))
  (if (= pasukimass 0) (setq P11  0 P12 1  P21 -1 P22 0))
  (if (= pasukimass 1) (setq P11 -1 P12 0  P21 0  P22 -1))
  (if (= pasukimass 2) (setq P11 0  P12 -1 P21 1  P22 0))
  (setq xx1 x1  yy1 y1 xx2 (+ (* x2 P11) (* y2 P21)) yy2 (+ (* x2 P12) (* y2 P22))
	xx3 (+ (* x3 P11) (* y3 P21)) yy3 (+ (* x3 P12) (* y3 P22)) )
(command "ucsicon" "off")  (command "limits" (list -13 -13) (list 13 13))
(command "zoom" "window" (list -13 -13) (list 13 13) )
(command "grid" 1) (command "grid" "on")
(command "snap" 1) (command "snap" "off") (setvar "osmode" 0)
(command "erase" "all" "") (command "color" "Red" )
(command "text" (list -13 12)  0.5 0 "Pasukimo apie koordinaciu pradzia transformacijos matrica")
(command "line" '(-10 0) '(10 0) "") (command "line" '(0 -10) '(0 10) "")
(command "pline" '(10 0) "w" 0.5 0 '(11 0) "")
(command "pline" '(0 10) "w" 0.5 0 '(0 11) "")
(setvar "pdmode" 2) (setvar "pdsize" -3)
(setq x -10) (setq y -10) (command "color" "Magenta" )
(command "point" (list x1 y1)) (command "point" (list xx1 yy1)) 
(repeat 20 (command "point" (list 0 y)(command "point" (list x 0))  )
  (setq x (+ x 1)) (setq y (+ y 1)))
  (setq x -10) (setq y -10) (command "color" "Blue" )
(repeat 11 (command "text" "j" "mc" (list -1 y) 0.5 0 X)
   (command "text" "j" "c" (list x -1) 0.5 0 y)
   (setq x (+ x 2)) (setq y (+ y 2)))
(command "line" (list x1 y1) (list x2 y2) (list x3 y3) "c") (command "color" "Green" )
(command "line" (list xx1 yy1) (list xx2 yy2) (list xx3 yy3) "c")
(command "zoom" "all")  (command "color" "Red" ) (command "text" (list 5 1)  0.8 0 "Yra")
  (if (= pasukimass 0) (command "text" (list -2 5)     0.6 90  "Reikia"))
  (if (= pasukimass 1) (command "text" (list -5 -1.5)  0.6 180 "Reikia"))
  (if (= pasukimass 2) (command "text" (list 1 -5)     0.6 270 "Reikia"))
(prompt "\nIveskite pasukimo apie koordinaciu pradzia transformacijos matricos 1-os eilutes elementus:")
  (setq M11 (getreal "\n1-ojo elemento reiksme: "))
  (setq M12 (getreal "2-ojo elemento reiksme: "))
  (setq M13 (getreal "3-ojo elemento reiksme: "))
(prompt "\nIveskite pasukimo apie koordinaciu pradzia transformacijos matricos 2-os eilutes elementus:")
  (setq M21 (getreal "\n1-ojo elemento reiksme: "))
  (setq M22 (getreal "2-ojo elemento reiksme: "))
  (setq M23 (getreal "3-ojo elemento reiksme: "))
(prompt "\nIveskite pasukimo apie koordinaciu pradzia transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* 1 0))) (setq yyy1 (+ (* x1 M12) (* y1 M22) (* 1 0)))
(setq xxx2 (+ (* x2 M11) (* y2 M21) (* 1 0))) (setq yyy2 (+ (* x2 M12) (* y2 M22) (* 1 0)))
(setq xxx3 (+ (* x3 M11) (* y3 M21) (* 1 0))) (setq yyy3 (+ (* x3 M12) (* y3 M22) (* 1 0)))
(command "color" "Red" )
(if (and (= xxx1 xx1) (= yyy1 yy1) (= xxx2 xx2) (= yyy2 yy2)(= xxx3 xx3)(= yyy3 yy3)
	 (= M31 0) (= M32 0) (= M33 1)) (setq rezultatas2 1) (setq rezultatas2 0))
(if (= rezultatas2 1)   (command "text" (list -12 9) 2 0 "TEISINGAI!")
 			(command "text" (list -12 9) 2 0 "KLAIDINGAI!"))
  (command "pline" (list xxx1 yyy1) "w" 0.2 0.2 (list xxx2 yyy2) (list xxx3 yyy3) "c")
)
; mastelio transformacijos matrica
(defun c:mastelis (/ x1 y1 x2 y2 x3 y3 x4 y4 xx1 yy1 xx2 yy2 xx3 yy3 xx4 yy4 xxx1 yyy1 xxx2 yyy2
	    xxx4 yyy4 x y m11 m12 m13 m21 m22 m23 m31 m32 m33 SX SY masteliss)
(setq x1 2 y1 2 x2 4 y2 2 x3 4 y3 4 x4 2 y4 4)
(command "color" "Red" )
(setq variantas3 (getint "\nNurodykite varianta - iveskite destytojo nurodyta numeri: "))
(setq masteliss (rem variantas3 4))
(if (= masteliss 0) (setq SX 2 SY 3)) (if (= masteliss 1) (setq SX 3 SY 2))
(if (= masteliss 2) (setq SX 3 SY 1)) (if (= masteliss 3) (setq SX 4 SY 3))
(setq xx1 (* x1 SX) yy1 (* y1 SY) xx2 (* x2 SX) yy2 (* y2 SY) xx3 (* x3 SX) yy3 (* y3 SY)
      xx4 (* x4 SX) yy4 (* y4 SY))
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "text" (list -1 20)  0.8 0 "Mastelio transformacijos matrica")
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) (list x4 y4) "c")
(command "color" "Green")
(command "line" (list xx1 yy1) (list xx2 yy2) (list xx3 yy3) (list xx4 yy4) "c")
(command "color" "Red" )
(command "text" "j" "mc" (list (+ x1 1) (+ y1 1))  0.6 0 "Yra")
(command "text" "j" "a" (list (+ xx1 0.5) (+ yy1 0.7)) (list (- xx2 0.5) (+ yy1 0.7)) "Reikia" 1 0 )
(prompt "\nIveskite mastelio transformacijos matricos 1-os eilutes elementus:")
(setq M11 (getreal "\n1-ojo elemento reiksme: "))
(setq M12 (getreal "2-ojo elemento reiksme: "))
(setq M13 (getreal "3-ojo elemento reiksme: "))
(prompt "\nIveskite mastelio transformacijos matricos 2-os eilutes elementus:")
(setq M21 (getreal "\n1-ojo elemento reiksme: "))
(setq M22 (getreal "2-ojo elemento reiksme: "))
(setq M23 (getreal "3-ojo elemento reiksme: "))
(prompt "\nIveskite mastelio transformacijos matricos 3-os eilutes elementus:")
(setq M31 (getreal "\n1-ojo elemento reiksme: "))
(setq M32 (getreal "2-ojo elemento reiksme: "))
(setq M33 (getreal "3-ojo elemento reiksme: "))
(setq xxx1 (* x1 M11)) (setq yyy1 (* y1 M22))
(setq xxx2 (* x2 M11)) (setq yyy2 (* y2 M22))
(setq xxx3 (* x3 M11)) (setq yyy3 (* y3 M22))
(setq xxx4 (* x4 M11)) (setq yyy4 (* y4 M22))
(command "color" "Red" )
(if (and (= xxx1 xx1) (= yyy1 yy1) (= xxx2 xx2) (= yyy2 yy2)(= xxx3 xx3)(= yyy3 yy3)
	 (= yyy4 yy4) (= M21 0) (= M12 0) (= M13 0)
	 (= M31 0) (= M32 0) (= M33 1)) (setq rezultatas3 1) (setq rezultatas3 0))
(if (= rezultatas3 1)   (command "text" (list 2 17) 2.5 0 "TEISINGAI!")
		 	(command "text" (list 2 17) 2.5 0 "KLAIDINGAI!"))
(command "pline" (list xxx1 yyy1) "w" 0.2 0.2 (list xxx2 yyy2) (list xxx3 yyy3)
	 (list xxx4 yyy4) "c")
)
; sutapdintu transformaciju kompozicijos matrica
(defun c:kompozicija (/ x1 y1 x2 y2 x3 y3 xx1 yy1 xx2 yy2 xx3 yy3 xxx1 yyy1 xxx2 yyy2
	    x y m11 m12 m13 m21 m22 m23 m31 m32 m33 TX TY)
(setq x1 2 y1 3 x2 4 y2 5 x3 4 y3 1)
(command "color" "Red" )
(setq variantas4 (getint "\nNurodykite varianta - iveskite destytojo nurodyta numeri: "))
(setq kompozicijaa (rem variantas4 4))
(if (= kompozicijaa 0) (setq XX1 4 YY1 8 XX2 2 YY2 4 XX3 2 YY3 12))
(if (= kompozicijaa 1) (setq XX1 9 YY1 5 XX2 5 YY2 4 XX3 5 YY3 6))
(if (= kompozicijaa 2) (setq XX1 10 YY1 4 XX2 6 YY2 6 XX3 14 YY3 6))
(if (= kompozicijaa 3) (setq XX1 10 YY1 4 XX2 14 YY2 2 XX3 6 YY3 2))
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "text" (list -2 20)  0.6 0 "Sutapdintu transformaciju kompozicijos matrica")
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) "c") (command "color" "Green")
(command "line" (list xx1 yy1) (list xx2 yy2) (list xx3 yy3) "c")
(command "color" "Red" )
(command "text" "j" "mc"(list (+ x1 2) y1)  0.8 0 "Yra")
(command "text" "j" "mc"(list (+ xx1 2) yy1)  0.6 0 "Reikia")
(prompt "\nIveskite sutapdintu transformaciju kompozicijos matricos 1-os eilutes elementus:")
  (setq M11 (getreal "   \n1-ojo elemento reiksme: "))
  (setq M12 (getreal "   2-ojo elemento reiksme: "))
  (setq M13 (getreal "   3-ojo elemento reiksme: "))
(prompt "\nIveskite sutapdintu transformaciju kompozicijos matricos 2-os eilutes elementus:")
  (setq M21 (getreal "   \n1-ojo elemento reiksme: "))
  (setq M22 (getreal "   2-ojo elemento reiksme: "))
  (setq M23 (getreal "   3-ojo elemento reiksme: "))
(prompt "\nIveskite sutapdintu transformaciju kompozicijos matricos 3-os eilutes elementus:")
  (setq M31 (getreal "   \n1-ojo elemento reiksme: "))
  (setq M32 (getreal "   2-ojo elemento reiksme: "))
  (setq M33 (getreal "   3-ojo elemento reiksme: "))
(setq xxx1 (+ (* x1 M11) (* y1 M21) (* 1 M31 ))) (setq yyy1 (+ (* x1 M12) (* y1 M22) (* 1 M32)))
(setq xxx2 (+ (* x2 M11) (* y2 M21) (* 1 M31 ))) (setq yyy2 (+ (* x2 M12) (* y2 M22) (* 1 M32)))
(setq xxx3 (+ (* x3 M11) (* y3 M21) (* 1 M31 ))) (setq yyy3 (+ (* x3 M12) (* y3 M22) (* 1 M32)))
(command "color" "Red" )
(if (and (= xxx1 xx1) (= yyy1 yy1) (= xxx2 xx2) (= yyy2 yy2)(= xxx3 xx3)(= yyy3 yy3)
	 (= M33 1)) (setq rezultatas4 1) (setq rezultatas4 0))
(if (= rezultatas4 1)  	(command "text" (list 2 17) 2.5 0 "TEISINGAI!")
		 	(command "text" (list 2 17) 2.5 0 "KLAIDINGAI!"))
(command "pline" (list xxx1 yyy1) "w" 0.2 0.2 (list xxx2 yyy2) (list xxx3 yyy3) "c")
)
; rezultatu patikra
(defun c:patikra (/ atgarsis)
(textscr)
(setq atgarsis (getvar "cmdecho")) (setvar "cmdecho" 0)
 (command "color" "Red" ) (princ "  \nKompiuterio Nr= ") (princ variantas1)
(if ( and (= rezultatas1 rezultatas2  rezultatas3 rezultatas4 1)
	  (= variantas1 variantas2 variantas3 variantas4))
  (princ "\nVisos transformacijos atliktos teisingai  -   DARBAS UZSKAITOMAS"))
(if (not (and (= variantas1 variantas2 variantas3 variantas4)))
  (princ "\nUzduociu variantai skirtingi arba ne visi atlikti - DARBAS NEUZSKAITOMAS"))
(if (and (= rezultatas1 1) (= variantas1 variantas1))
  (princ "\nPerkelimo   transformacijos matrica sudaryta  TEISINGAI")
  (princ "\nPerkelimo   transformacijos matrica sudaryta  KLAIDINGAI"))
(if (and (= rezultatas2 1) (= variantas2 variantas1))
  (princ "\nPasukimo    transformacijos matrica sudaryta  TEISINGAI")
  (princ "\nPasukimo    transformacijos matrica sudaryta  KLAIDINGAI"))  
(if (and (= rezultatas3 1) (= variantas3 variantas1))
  (princ "\nMastelio    transformacijos matrica sudaryta  TEISINGAI")
  (princ "\nMastelio    transformacijos matrica sudaryta  KLAIDINGAI"))
(if (and (= rezultatas4 1) (= variantas4 variantas1))
  (princ "\nTransformaciju kompozicijos matrica sudaryta  TEISINGAI\n")
  (princ "\nTransformaciju kompozicijos matrica sudaryta  KLAIDINGAI\n"))
(setvar "cmdecho" atgarsis)
)

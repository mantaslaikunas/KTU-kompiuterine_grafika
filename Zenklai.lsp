(DEFUN C:Zenklai()
  (setq taskas (getpoint "\nIveskite bazinio tasko pradine koordinate:"))
    (COMMAND "CHPROP" sel "" "COLOR" "BYLAYER" "LWEIGHT" "0.30" "LTYPE" "BYLAYER" "")
  ;Vyras
  (setq galva (list (+ (car taskas) 0) (+ (cadr taskas) 0)))
  (setq torso1 (list (+ (car galva) 0) (- (cadr galva) 11)))
  (setq torso2 (list (+ (car taskas) 0) (- (cadr taskas) 55)))
  (setq Dkoja1 (list (- (car torso2) 5) (+ (cadr torso2) 0)))
  (setq Dkoja2 (list (+ (car Dkoja1) 0) (- (cadr Dkoja1) 40)))
  (setq Kkoja1 (list (+ (car torso2) 5) (+ (cadr torso2) 0)))
  (setq Kkoja2 (list (+ (car Kkoja1) 0) (- (cadr Kkoja1) 40)))
  (setq Dpetys1 (list (- (car torso1) 12) (- (cadr torso1) 3)))
  (setq Dpetys2 (list (- (car Dpetys1) 11) (+ (cadr Dpetys1) 0)))
  (setq Kpetys1 (list (+ (car torso1) 12) (- (cadr torso1) 3)))
  (setq Kpetys2 (list (+ (car Kpetys1) 11) (+ (cadr Kpetys1) 0)))
  (setq Dranka1 (list (+ (car Dpetys2) 5) (+ (cadr Dpetys2) 0)))
  (setq Dranka2 (list (+ (car Dranka1) 0) (- (cadr Dranka1) 35)))
  (setq Kranka1 (list (- (car Kpetys2) 5) (+ (cadr Kpetys2) 0)))
  (setq Kranka2 (list (+ (car Kranka1) 0) (- (cadr Kranka1) 35)))
  (command "circle" galva 11 -enter)
  (command "pline" torso1 "w" 25 20 torso2 -enter)
  (command "pline" Kkoja1 "w" 8 7 Kkoja2 -enter)
  (command "pline" Dkoja1 "w" 8 7 Dkoja2 -enter)
  (command "pline" Dpetys1 "w" 6 6 Dpetys2 -enter)
  (command "pline" Kpetys1 "w" 6 6 Kpetys2 -enter)
  (command "pline" Dranka1 "w" 10 6 Dranka2 -enter)
  (command "pline" Kranka1 "w" 10 6 Kranka2 -enter)
  (setq Akiniai01 (list (+ (car Galva) 5) (+ (cadr Galva) 0)))
  (setq Akiniai11 (list (+ (car Akiniai01) 0) (- (cadr Akiniai01) 3)))
  (setq Akiniai02 (list (- (car Galva) 5) (+ (cadr Galva) 0)))
  (setq Akiniai22 (list (+ (car Akiniai02) 0) (- (cadr Akiniai02) 3)))
  (command "circle" Akiniai01 3 -enter)
  (command "circle" Akiniai02 3 -enter)
  (command "fillet" "R" (/ 3) )
  (command "fillet" Akiniai11 Akiniai22 -enter)
  ;Moteris
  (setq galva (list (+ (car taskas) 60) (+ (cadr taskas) 0)))
  (setq torso1 (list (+ (car galva) 0) (- (cadr galva) 11)))
  (setq torso2 (list (+ (car galva) 0) (- (cadr galva) 55)))
  (setq Dkoja1 (list (- (car torso2) 5) (+ (cadr torso2) 0)))
  (setq Dkoja2 (list (+ (car Dkoja1) 0) (- (cadr Dkoja1) 40)))
  (setq Kkoja1 (list (+ (car torso2) 5) (+ (cadr torso2) 0)))
  (setq Kkoja2 (list (+ (car Kkoja1) 0) (- (cadr Kkoja1) 40)))
  (setq Dpetys1 (list (- (car torso1) 10) (- (cadr torso1) 3)))
  (setq Dpetys2 (list (- (car Dpetys1) 7) (+ (cadr Dpetys1) 0)))
  (setq Kpetys1 (list (+ (car torso1) 10) (- (cadr torso1) 3)))
  (setq Kpetys2 (list (+ (car Kpetys1) 7) (+ (cadr Kpetys1) 0)))
  (setq Dranka1 (list (+ (car Dpetys2) 3) (+ (cadr Dpetys2) 0)))
  (setq Dranka2 (list (- (car Dranka1) 5) (- (cadr Dranka1) 35)))
  (setq Kranka1 (list (- (car Kpetys2) 3) (+ (cadr Kpetys2) 0)))
  (setq Kranka2 (list (+ (car Kranka1) 5) (- (cadr Kranka1) 35)))
  (command "circle" galva 11 -enter)
  (command "pline" torso1 "w" 20 30 torso2 -enter)
  (command "pline" Kkoja1 "w" 6 5 Kkoja2 -enter)
  (command "pline" Dkoja1 "w" 6 5 Dkoja2 -enter)
  (command "pline" Dpetys1 "w" 5 5 Dpetys2 -enter)
  (command "pline" Kpetys1 "w" 5 5 Kpetys2 -enter)
  (command "pline" Dranka1 "w" 6 5 Dranka2 -enter)
  (command "pline" Kranka1 "w" 6 5 Kranka2 -enter)
  (setq Akiniai01 (list (+ (car Galva) 5) (+ (cadr Galva) 0)))
  (setq Akiniai11 (list (+ (car Akiniai01) 0) (- (cadr Akiniai01) 3)))
  (setq Akiniai02 (list (- (car Galva) 5) (+ (cadr Galva) 0)))
  (setq Akiniai22 (list (+ (car Akiniai02) 0) (- (cadr Akiniai02) 3)))
  (command "circle" Akiniai01 3 -enter)
  (command "circle" Akiniai02 3 -enter)
  (command "fillet" "R" (/ 3) )
  (command "fillet" Akiniai11 Akiniai22 -enter)
  (setq Kepure1 (list (+ (car Galva) 0) (+ (cadr Galva) 15)))
  (setq Kepure2 (list (+ (car Galva) 0) (+ (cadr Galva) 5)))
  (command "pline" Kepure2 "w" 30 0 Kepure1 -enter)
)
